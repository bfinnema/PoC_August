module infra_pe_cfs {

  namespace "http://example.com/infra_pe_cfs";
  prefix infra_pe_cfs;

  import ietf-inet-types {
    prefix inet;
  }
  import tailf-common {
    prefix tailf;
  }
  import tailf-ncs {
    prefix ncs;
  }

  description
    "Infrastructure CFS for PE routers";

  revision 2024-03-01 {
    description
      "Initial revision.";
  }

  grouping interface_grouping {
    leaf interface_name {
      tailf:info "Interface name. For example TenGigE.";
      type enumeration {
        enum FastEthernet;
        enum GigabitEthernet;
        enum TenGigE;
        enum TwentyFiveGigE;
        enum FortyGigE;
        enum FiftyGigE;
        enum HundredGigE;
        enum TwoHundredGigE;
        enum FourHundredGigE;
        enum EightHundredGigE;
      }
      mandatory true;
    }
    leaf interface_number {
      tailf:info "Interface number. For example 0 or 1/0";
      type string {
        pattern "[0-9]{1,2}(/[0-9]{1,2}){1,4}";
      }
      mandatory true;
    }
    leaf ipv4_address {
      tailf:info "Interface IPv4 address.";
      type inet:ipv4-address;
    }
    leaf ipv4_mask {
      tailf:info "Interface IPv4 mask.";
      type inet:ipv4-address;
    }
    leaf interface_description {
      tailf:info "Interface description.";
      type string;
    }
  }

  list infra_pe_cfs {
    description "This is an RFS skeleton service";

    key name;
    leaf name {
      tailf:info "Unique service id";
      tailf:cli-allow-range;
      type string;
    }

    uses ncs:service-data;
    ncs:servicepoint infra_pe_cfs-servicepoint;

    leaf device {
      type leafref {
        path "/ncs:devices/ncs:device/ncs:name";
      }
    }

    leaf as_number {
      tailf:info "Autonomous System number eg 65000";
      type uint16;
      mandatory true;
    }

    leaf rr1_ipv4_address {
      tailf:info "Address of Route Reflector 1";
      type inet:ipv4-address;
    }

    leaf rr2_ipv4_address {
      tailf:info "Address of Route Reflector 2";
      type inet:ipv4-address;
    }

    leaf isis_process_id {
      tailf:info "ISIS process ID";
      type string;
    }

    /* leaf net_id {
      tailf:info "ISIS NET ID Format sample 49.0002.2131.6711.5202.00";
      type string;
    } */

    leaf loopback0_ipv4_address {
      tailf:info "IPv4 address of Loopback0";
      type inet:ipv4-address;
    }

    list interfaces {
      key interface_number;
      uses interface_grouping;
    }
  }
}
