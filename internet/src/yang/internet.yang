module internet {

  namespace "http://example.com/internet";
  prefix internet;

  import ietf-inet-types {
    prefix inet;
  }
  import tailf-common {
    prefix tailf;
  }
  import tailf-ncs {
    prefix ncs;
  }

  description
    "Internet Service";

  revision 2024-07-13 {
    description
      "Initial revision.";
  }

  grouping interface_grouping {
    leaf interface_name {
      tailf:info "Interface name. For example GigabitEthernet.";
      type enumeration {
        enum FastEthernet;
        enum GigabitEthernet;
        enum TenGigE;
        enum TwentyFiveGigE;
        enum FortyGigE;
        enum FiftyGigE;
        enum HundredGigE;
        enum TwoHundredGigE;
        enum FourHundredGigE;
        enum EightHundredGigE;
        enum xe;
      }
    }
    leaf interface_number {
      tailf:info "Interface number. For example 0/0/0/9";
      type string {
        pattern "[0-9]{1,2}(/[0-9]{1,2}){1,4}";
      }
    }
    leaf ipv4_address {
      tailf:info "Interface IPv4 address.";
      type inet:ipv4-address;
    }
    leaf ipv4_mask {
      tailf:info "Interface IPv4 mask.";
      type inet:ipv4-address;
    }
    leaf interface_description {
      tailf:info "Interface description.";
      type string;
    }
  }

  list internet {
    description "This is an RFS skeleton service";

    key name;
    leaf name {
      tailf:info "Unique service id";
      tailf:cli-allow-range;
      type string;
    }

    uses ncs:service-data;
    ncs:servicepoint internet-servicepoint;

    leaf pe_device {
      type leafref {
        path "/ncs:devices/ncs:device/ncs:name";
      }
    }

    leaf sw_device {
      type leafref {
        path "/ncs:devices/ncs:device/ncs:name";
      }
    }

    leaf vlan_id {
      tailf:info "VLAN ID eg 51";
      type uint16;
      mandatory true;
    }

    leaf as_number {
      tailf:info "Autonomous System number eg 100";
      type uint16;
      mandatory true;
    }

    leaf customer_as {
      tailf:info "Remote Autonomous System number eg 65051";
      type uint16;
      mandatory true;
    }

    container pe_interface {
      uses interface_grouping;
    }

    container sw_interface {
      uses interface_grouping;
    }
  }
}
