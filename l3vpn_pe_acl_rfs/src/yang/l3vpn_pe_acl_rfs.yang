module l3vpn_pe_acl_rfs {

  namespace "http://example.com/l3vpn_pe_acl_rfs";
  prefix l3vpn_pe_acl_rfs;

  import ietf-inet-types {
    prefix inet;
  }
  import tailf-common {
    prefix tailf;
  }
  import tailf-ncs {
    prefix ncs;
  }
  import inventory {
    prefix inventory;
  }

  description
    "RFS that adds an ACL to the PE interface of a L3VPN service";

  revision 2024-07-26 {
    description
      "Initial revision.";
  }

  grouping interface_grouping {
    leaf interface_name {
      tailf:info "Interface name. For example TenGigE.";
      type enumeration {
        enum FastEthernet;
        enum GigabitEthernet;
        enum TenGigE;
        enum TwentyFiveGigE;
        enum FortyGigE;
        enum FiftyGigE;
        enum HundredGigE;
        enum TwoHundredGigE;
        enum FourHundredGigE;
        enum EightHundredGigE;
        enum xe;
      }
    }
    leaf interface_number {
      tailf:info "Interface number. For example 0 or 1/0";
      type string {
        pattern "[0-9]{1,2}(/[0-9]{1,2}){1,4}";
      }
    }
  }

  list l3vpn_pe_acl_rfs {
    description "This is an RFS skeleton service";

    key name;
    leaf name {
      tailf:info "Unique service id";
      tailf:cli-allow-range;
      type string;
    }

    uses ncs:service-data;
    ncs:servicepoint l3vpn_pe_acl_rfs-servicepoint;

    leaf device {
      type leafref {
        path "/ncs:devices/ncs:device/ncs:name";
      }
    }

    leaf acl_name {
      tailf:info "The ACL to be used.";
      type leafref {
        path "/inventory:inventory/inventory:access_lists/inventory:access_list/inventory:acl_name";
      }
    }

    leaf vlan_id {
      tailf:info "VLAN ID to be used as sub-interface number and for dot1q encapsulation";
      type uint16;
    }

    container interface {
      uses interface_grouping;
    }
  }
}
